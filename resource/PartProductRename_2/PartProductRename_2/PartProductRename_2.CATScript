'==============================================
' PartProductRename
' - rename selected products, parts, components
'
' Version: 2
'------------------------------
'
'   This program is distributed under the terms of the GNU General
'   Public License
'   Copyright 2011 Dirk Schuster [meisterlumpi@riotdowntown.com]
'
'   This program is free software: you can redistribute it and/or modify
'   it under the terms of the GNU General Public License as published by
'   the Free Software Foundation, either version 3 of the License, or
'   (at your option) any later version.
'
'   This program is distributed in the hope that it will be useful,
'   but WITHOUT ANY WARRANTY; without even the implied warranty of
'   MERCHANTABILITY or FITNESS FOR A PARTICULAR PURPOSE.  See the
'   GNU General Public License for more details.
'
'   You should have received a copy of the GNU General Public License
'   along with this program.  If not, see <http://www.gnu.org/licenses/>.
'
'------------------------------

Option Explicit

'############################################
'#            -- OPTIONS --                 #
'############################################
Function NewName(iOldName As String) As String
    ' SAMPLES:
    ' ========
    ' static name
    NewName = "RCC1_" & iOldName & ""
    
    ' inputbox
  ''NewName = InputBox("Enter new name:", "New name", iOldName)
  ''If NewName = "" Then NewName = iOldName
    
    ' reverse the name.. i.e. Body1 -> 1ydoB
  ''Dim i As Integer
  ''NewName = ""
  ''For i = 1 To Len(iOldName)
  ''    NewName = NewName & Left(Right(iOldName, i), 1)
  ''Next
End Function
'############################################

Sub CATMain()
    Dim i As Integer
   On Error Resume Next
    Dim ActiveDocument1 As Document
      Set ActiveDocument1 = CATIA.ActiveDocument
   If Err.Number <> 0 Then
       ' in case no open document was found
       ' ...
       '''Err.Clear
       Call MsgBox("No document was found.", _
                   vbCritical + vbOKOnly, "Error")
       Exit Sub
   End If
    Dim Selection1 As Selection
      Set Selection1 = ActiveDocument1.Selection
    
    If Selection1.Count <> 0 Then
        Dim Product1 As Product
        ' check document type for active document
        If TypeName(ActiveDocument1) = "ProductDocument" Then
            ' active document is a product
            For i = 1 To Selection1.Count
                With Selection1.Item(i)
                    ' check selected element
                    If TypeName(.Value) = "Product" Then
                        Set Product1 = .Value
                        If TypeName(Product1.Parent.Parent) = "Application" Then
                            ' if item is main document
                            Product1.PartNumber = NewName(Product1.PartNumber)
                        Else
                            ' if item is a subproduct
                            Set Product1 = _
                                Product1.Parent.Parent.ReferenceProduct.Products.Item(Product1.Name)
                            Product1.Name = NewName(Product1.Name)
                        End If
                    Else
                        .Value.Name = NewName(.Value.Name)
                    End If
                End With
            Next
        ElseIf TypeName(ActiveDocument1) = "PartDocument" Then
            ' active document is a part
            Set Product1 = ActiveDocument1.GetItem(ActiveDocument1.Part.Name)
            For i = 1 To Selection1.Count
                With Selection1.Item(i)
                    ' check selected element
                    If TypeName(.Value) = "Part" Then
                        ' if item is the part itself
                        Product1.PartNumber = NewName(Product1.PartNumber)
                    Else
                        .Value.Name = NewName(.Value.Name)
                    End If
                End With
            Next
        Else
            ' active document is neither product nor part
            Call MsgBox("Macro only works with product- or part documents.", _
                        vbCritical + vbOKOnly, "Error")
        End If
        
        Set Product1 = Nothing
        Set Selection1 = Nothing
       If Err.Number <> 0 Then
           ' in case there was an error
           ' ...
           Err.Clear
       End If
    Else
        Call MsgBox("No selected elements found, " & _
                    "select something first.", _
                    vbCritical + vbOKOnly, "Error")
    End If
End Sub
